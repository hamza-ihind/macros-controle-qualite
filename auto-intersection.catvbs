Dim gTotal
Dim gFailed
Dim gReport

' Entry point: detects auto-intersecting surfaces in the active document.
Sub CATMain()
    Dim oDoc
    Dim sType

    gTotal  = 0
    gFailed = 0
    gReport = ""

    Set oDoc = CATIA.ActiveDocument
    sType = TypeName(oDoc)

    If sType = "PartDocument" Then
        ProcessPart oDoc.Part
    ElseIf sType = "ProductDocument" Then
        ScanProduct oDoc.Product
    Else
        MsgBox "Type de document non pris en charge." & vbCrLf & _
               "Veuillez ouvrir un fichier CATPart ou CATProduct.", _
               vbExclamation, "Controle Auto-Intersection"
        Exit Sub
    End If

    Dim sHeader
    Dim sSep   
    sSep = String(52, "-") & vbCrLf

    If gTotal = 0 Then
        MsgBox "Aucune surface detectable n'a ete trouvee dans le document." & vbCrLf & _
               "Verifiez que le document contient des corps geometriques.", _
               vbInformation, "Controle Auto-Intersection"
    ElseIf gFailed = 0 Then
        sHeader = "RESULTAT : Toutes les surfaces sont valides." & vbCrLf & _
                  gTotal & " surface(s) analysee(s) -- 0 defaut detecte." & vbCrLf & _
                  sSep
        MsgBox sHeader & gReport, vbInformation, "Controle Auto-Intersection"
    Else
        sHeader = "RESULTAT : Auto-intersection(s) detectee(s) !" & vbCrLf & _
                  gFailed & " surface(s) en defaut sur " & gTotal & " analysee(s)." & vbCrLf & _
                  sSep
        MsgBox sHeader & gReport, vbCritical, "Controle Auto-Intersection"
    End If
End Sub

' Recursively scans a Product tree and processes each Part found.
Sub ScanProduct(oProd)
    Dim i     
    Dim oChild
    Dim oDoc  
    Dim sType 

    For i = 1 To oProd.Products.Count
        Set oChild = oProd.Products.Item(i)
        sType = ""
        On Error Resume Next
        Set oDoc = oChild.ReferenceProduct.Parent
        sType = TypeName(oDoc)
        On Error GoTo 0
        If sType = "PartDocument" Then
            ProcessPart oDoc.Part
        Else
            ScanProduct oChild
        End If
    Next
End Sub

' Processes a Part's HybridBodies for auto-intersection checks.
Sub ProcessPart(oPart)
    If oPart.HybridBodies.Count > 0 Then
        ScanHybridBodies oPart.HybridBodies, oPart
    End If
End Sub

' Iterates all HybridShapes (including nested bodies) and checks each one.
Sub ScanHybridBodies(oHBs, oPart)
    Dim oHB
    Dim k  
    Dim oHS

    For Each oHB In oHBs
        For k = 1 To oHB.HybridShapes.Count
            Set oHS = oHB.HybridShapes.Item(k)
            CheckSurface oHS, oPart
        Next
        If oHB.HybridBodies.Count > 0 Then
            ScanHybridBodies oHB.HybridBodies, oPart
        End If
    Next
End Sub

' Checks a single surface for auto-intersection using a temporary Join feature.
Sub CheckSurface(oHS, oPart)
    Dim oSPA   
    Dim oRef   
    Dim oMeas  
    Dim dArea  
    Dim oHSF
    Dim oTmpHB
    Dim oJoin
    Dim oSel
    Dim bFailed

    dArea = 0
    On Error Resume Next
    Set oSPA  = oPart.Parent.GetWorkbench("SPAWorkbench")
    Set oRef  = oPart.CreateReferenceFromObject(oHS)
    Set oMeas = oSPA.GetMeasurable(oRef)
    dArea = oMeas.Area
    On Error GoTo 0

    If dArea <= 0 Then Exit Sub

    gTotal = gTotal + 1

    Set oHSF   = oPart.HybridShapeFactory
    Set oRef   = oPart.CreateReferenceFromObject(oHS)
    Set oTmpHB = oPart.HybridBodies.Add()
    oTmpHB.Name = "TMP_AI"
    Set oJoin  = oHSF.AddNewJoin(oRef, oRef)
    oTmpHB.AppendHybridShape oJoin

    bFailed = False
    On Error Resume Next
    oPart.UpdateObject oJoin
    If Err.Number <> 0 Then bFailed = True
    Err.Clear
    On Error GoTo 0

    Dim sName  
    Dim sPad   
    Dim sStatus
    sName = oHS.Name
    If Len(sName) < 40 Then
        sPad = Space(40 - Len(sName))
    Else
        sPad = " "
    End If

    If bFailed Then
        gFailed = gFailed + 1
        sStatus = "Auto-Intersectante"
        gReport = gReport & "  " & sName & sPad & "-->  " & sStatus & vbCrLf
    Else
        sStatus = "OK"
        gReport = gReport & "  " & sName & sPad & "-->  " & sStatus & vbCrLf
    End If

    On Error Resume Next
    Set oSel = oPart.Parent.Selection
    oSel.Clear
    oSel.Add oTmpHB
    oSel.Delete
    oPart.Update
    On Error GoTo 0
End Sub
